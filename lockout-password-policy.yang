submodule msw-lockout-password-policy {
	namespace "http://cisecurity.org/yang/microsoft-windows-configuration";
	prefix msw-lpp;

	belongs-to "sacm-core" {
		prefix "sacm-core";
	}

	import "ietf-yang-types" {
		prefix "yang";
	}

	// Do any other modules need inclusion?

	organization "Center for Internet Security";
	contact yang@cisecurity.org;
	description "";
	revision 2018-06-06 {
		description 
			"Initial Version; Describing Audit Policy configuration information that can be collected from Microsoft Windows systems";
	}


	//
	// Types
	//

	//
	// Groupings
	//
	grouping lockout-policy {
		description "Enumerates various attributes associated with lockout information for users and global groups in the security database.";
		grouping force-logoff {
			description "Specifies, in seconds (from a DWORD), the amount of time between the end of the valid logon time and the 
				time when the user is forced to log off the network. A value of TIMEQ_FOREVER (max DWORD value, 4294967295) indicates 
				that the user is never forced to log off. A value of zero indicates that the user will be forced to log off immediately 
				when the valid logon time expires. See the USER_MODALS_INFO_0 structure returned by a call to NetUserModalsGet().";
			uses sacm-core:entity-int-type;
		}
		grouping lockout-duration {
			description "Specifies, in seconds, how long a locked account remains locked before it is automatically unlocked. See 
				the USER_MODALS_INFO_3 structure returned by a call to NetUserModalsGet().";
			uses sacm-core:entity-int-type;
		}
		grouping lockout-observation-window {
			description "Specifies the maximum time, in seconds, that can elapse between any two failed logon attempts before lockout 
				occurs. See the USER_MODALS_INFO_3 structure returned by a call to NetUserModalsGet().";
			uses sacm-core:entity-int-type;
		}
		grouping lockout-threshold {
			description "Specifies the number of invalid password authentications that can occur before an account is marked "locked out." 
				See the USER_MODALS_INFO_3 structure returned by a call to NetUserModalsGet().";
			uses sacm-core:entity-int-type;
		}
	}

	grouping password-policy {
		description "Specific policy items associated with passwords. It is important to note that these policies are specific to certain 
			versions of Windows. As a result, the documentation for that version of Windows should be consulted for more information. Information 
			is stored in the SAM or Active Directory but is encrypted or hidden so the 'registry' and 'active-directory are of no use. If this 
			can be figured out, then the password_policy item is not needed.";

		grouping max-password-age {
			description "Specifies, in seconds (from a DWORD), the maximum allowable password age. A value of TIMEQ_FOREVER (max DWORD value, 4294967295) 
				indicates that the password never expires. The minimum valid value for this element is ONE_DAY (86400). See the USER_MODALS_INFO_0 structure 
				returned by a call to NetUserModalsGet().";
			uses sacm-core:entity-int-type;
		}
		grouping min-password-age {
			description "Specifies the minimum number of seconds that can elapse between the time a password changes and when it can be changed again. 
				A value of zero indicates that no delay is required between password updates";
			uses sacm-core:entity-int-type;
		}
		grouping min-password-length {
			description "Specifies the minimum allowable password length. Valid values for this element are zero through PWLEN.";
			uses sacm-core:entity-int-type;
		}
		grouping password-history-length {
			description "Specifies the length of password history maintained. A new password cannot match any of the previous usrmod0_password_hist_len 
				passwords. Valid values for this element are zero through DEF_MAX_PWHIST.";
			uses sacm-core:entity-int-type;
		}
		grouping password-complexity {
			description "A boolean value that signifies whether passwords must meet the complexity requirements put forth by the operating system.";
			uses sacm-core:entity-boolean-type;
		}
		grouping reversible-encryption {
			description "Determines whether or not passwords are stored using reversible encryption.";
			uses sacm-core:entity-boolean-type;
		}
		grouping anonymous-name-lookup {
			description "Determines whether or not an anonymous user may query the local LSA policy";
			uses sacm-core:entity-boolean-type;
		}
	}

	//
	// System Characteristics
	//

	// Account Lockout Policy
	container lockout-policy-item {
		description "Enumerates various attributes associated with lockout information for users and global groups in the security database.";

		augment /sacm-core:item {
			uses lockout-policy;
		}
	}

	// Password Policy
	container password-policy-item {
		description "Specific policy items associated with passwords. It is important to note that these policies are specific to certain 
			versions of Windows. As a result, the documentation for that version of Windows should be consulted for more information. Information 
			is stored in the SAM or Active Directory but is encrypted or hidden so the 'registry' and 'active-directory are of no use. If this 
			can be figured out, then the password_policy item is not needed.";

		augment /sacm-core:item {
			uses password-policy;
		}
	}
}
