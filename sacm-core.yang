module sacm-core {
	namespace "http://cisecurity.org/yang/sacm-core";
	prefix "sacm-core";

	//import "ietf-yang-types" {
	//	prefix "yang";
	//}

	// include submodules
	//include user-rights-assignment;
	//include msw-audit-policy;
	//include msw-lockout-password-policy;

	organization "Center for Internet Security";
	contact yang@cisecurity.org;
	description "";
	revision 2018-06-06 {
		description 
			"Initial Version; Types, Groupings, and any other constructs common to SACM.  
			NOTE: Loosely maps to OVAL Common";
	}

	typedef entity-datatype {
		description "The entity-datatype simple type defines the legal datatypes that are used to describe the values of 
				     individual entities. A value should be interpreted according to the specified type. This is most important 
				     during comparisons. For example, is '21' less than '123'? will evaluate to true if the datatypes are 'int', 
				     but will evaluate to 'false' if the datatypes are 'string'. Another example is applying the 'equals' 
				     operation to '1.0.0.0' and '1.0'. With datatype 'string' they are not equal, with datatype 'version' 
				     they are.";
		type enumeration {
			enum binary;
			enum boolean;
			enum evr-string;
			enum fileset-revision;
			enum float;
			enum integer;
			enum ipv4;
			enum ipv6;
			enum string;
			enum version;
			enum record;
			enum debian-evr-string;
			enum cisco-ios-version;
		}
	}

	typedef entity-operation {
		description "Defines acceptable operations. Each operation defines how to compare entities against their actual values.";
		type enumeration {
			enum equals;
			enum not-equal;
			enum case-insensitive-equals;
			enum case-insensitive-not-equal;
			enum greater-than;
			enum greater-than-or-equal-to;
			enum less-than;
			enum less-than-or-equal-to;
			enum bitwise-and;
			enum bitwise-or;
			enum pattern-match;
			enum subset-of;
			enum superset-of;
		}
	}

	typedef entity-logical-operator {
		description "Operators describing the logical combination of results.  Each operator defines how to 
		evaluate multiple arguments.";

		type enumeration {
			enum AND {
				description "The AND operator produces a true result if every argument is true. If one or more 
				arguments are false, the result of the AND is false. If one or more of the arguments are unknown, 
				and if none of the arguments are false, then the AND operator produces a result of unknown.";
			}
			enum OR {
				description "The OR operator produces a true result if one or more arguments is true. If every 
				argument is false, the result of the OR is false. If one or more of the arguments are unknown and 
				if none of arguments are true, then the OR operator produces a result of unknown.";
			}
			enum XOR {
				description "XOR is defined to be true if an odd number of its arguments are true, and false otherwise. 
				If any of the arguments are unknown, then the XOR operator produces a result of unknown.";
			}
			enum ONE {
				description "The ONE operator produces a true result if one and only one argument is true. If there 
				are more than argument is true (or if there are no true arguments), the result of the ONE is false. 
				If one or more of the arguments are unknown, then the ONE operator produces a result of unknown.";
			}
		}
	}

	typedef entity-status {
		description "Defines the valid status messages associated with collection of specific information associated with an item.";
		type enumeration {
			enum error {
				description "A status of 'error' says that there was an error collecting information associated with an 
				item as a whole or any specific entity. An item would have a status of 'error' if a problem occurred that 
				prevented the item from being collected.";
			}
			enum exists {
				description "A status of 'exists' says that the item or specific piece of information exists on the system 
				and has been collected.";
			}
			enum does-not-exist {
				description "A status of 'does not exist' says that the item or specific piece of information does not 
				exist and therefore has not been collected. This status assumes that an attempt was made to collect the 
				information, but the information just does not exist.";
			}
			enum not-collected {
				description "A status of 'not collected' says that no attempt was made to collect the item or specific 
				piece of information so it is unknown what the value is and if it even exists.";
			}
		}
	}

	typedef message-level {
		description "Defines the different levels associated with a message. There is no specific criteria about which messages get assigned which level. This is completely 
		arbitrary and up to the content producer to decide what is an error message and what is a debug message.";

		type enumeration {
			enum debug {
				description "Debug messages should only be displayed by a tool when run in some sort of verbose mode.";
			}
			enum error {
				description "Error messages should be recorded when there was an error that did not allow the collection of specific data.";
			}
			enum fatal {
				description "A fatal message should be recorded when an error causes the failure of more than just a single piece of data.";
			}
			enum info {
				description "Info messages are used to pass useful information about the data collection to a user.";
			}
			enum warning {
				description "A warning message reports something that might not correct but information was still collected.";
			}
		}
	}

	typedef item-check {
		description "Defines acceptable check values, which are used to determine the final result of something based on the 
		results of individual components. When used to define the relationship between collected characteristics and expected 
		state, each check value defines how many of the matching objects (items except those with a status of does not exist) 
		must satisfy the given state for the test to return true. When used to define the relationship between instances of a 
		given entity, the different check values defines how many instances must be true for the entity to return true. When 
		used to define the relationship between entities and multiple variable values, each check value defines how many variable 
		values must be true for the entity to return true.";

		type enumeration {
			enum all {
				description "A value of 'all' means that a final result of true is given if all the individual results under consideration are true.";
			}
			enum at-least-one {
				description "A value of 'at-least-one' means that a final result of true is given if at least one of the individual results under consideration is true.";
			}
			enum none {
				description "A value of 'none' means that a final result of true is given if none the individual results under consideration are true.";
			}
			enum one {
				description "A value of 'one' means that a final result of true is given if one and only one of the individual results under consideration are true.";
			}
		}
	}

	typedef existence-check {
		description "Defines acceptable existence values, which are used to determine a result based on the existence of individual system characteristics items. 
		The main use for this is for a test regarding the existence of items on the system. Its secondary use is for a state regarding the existence of entities 
		within corresponding items.";

		type enumeration {
			enum all-exist {
				description "When used in the comparison of a system characteristics item element to an expected state, a value of 'all-exist' means that every item 
				entity for an object defined by the description exists on the system. When used in the context of a test's check-existence element, this value is 
				equivalent to 'at-least-one-exists' because non-existent items have no impact upon evaluation.";
			}
			enum any-exist {
				description "A value of 'any-exist' means that zero or more objects defined by the description exist on the system.";
			}
			enum at-least-one-exists {
				description "A value of 'at-least-one-exists' means that at least one object defined by the description exists on the system.";
			}
			enum none-exist {
				description "A value of 'none-exist' means that none of the objects defined by the description exist on the system.";
			}
			enum only-one-exists {
				description "A value of 'only-one-exists' means that only one object defined by the description exists on the system.";
			}
		}
	}

	//
	// Groupings
	//
	grouping entity-base-type {
		leaf entity-status {
			description "The determined collection status of the enclosing element";
			type entity-status;
		}
		leaf datatype {
			description "The assigned datatype of the enclosing element";
			type entity-datatype;
		}
		leaf operation {
			type entity-operation;
		}
		leaf nil {
			description "A boolean value illustrating whether or not the enclosing element was found to have a NULL value; different from an empty string";
			type boolean;
		}
	}

	grouping entity-int-type {
		uses entity-base-type;

		leaf entity-value {
			type int32;
		}
	}

	grouping entity-string-type {
		uses entity-base-type;

		leaf entity-value {
			type string;
		}
	}

	grouping entity-boolean-type {
		uses entity-base-type;

		leaf entity-value {
			type boolean;
		}
	}

	grouping entity-record-field-type {
		description "";

		leaf name {
			type string;
		}
		leaf value {
			type string;
		}
	}

	grouping entity-record-type {
		description "";

		uses entity-base-type;

		list fields {
			description "";
			key "name";
			uses entity-record-field-type;
		} 
	}

	grouping message {
		description "Defines the structure for which messages are relayed from the data collection engine. Each message is a text string that has 
		an associated level attribute identifying the type of message being sent. These messages could be error messages, warning messages, debug 
		messages, etc. How the messages are used by tools and whether or not they are displayed to the user is up to the specific implementation.";

		leaf message-index {
			type int32;
		}

		leaf message-level {
			type message-level;
		}

		leaf message-text {
			type string;
		}
	}

	grouping item {
		description "The abstract item element holds information about a specific item on a system. An item might be a file, a rpm, a process, etc. 
			This element is extended by the different component schemas through substitution groups. Each item represents a unique instance of an 
			object, such as a single file or a single user.";

		leaf item-id {
			description "The required id attribute is a unique (to the file) identifier that allows the specific item to be referenced.";
			type int32;
		}

		leaf item-status {
			description "The required status attribute holds information regarding the success of the data collection. For example, if an item 
				exists on the system then the status would reflect this with a value of 'exists'. If an error occurs which is not associated with 
				any item entities, or if an error occurs that is associated with an item entity matching an associated object entity, then the 
				status would be 'error'. An error specific to any particular entity should be addressed at the entity level and, for item entities 
				not associated with an object entity, not the item level. When creating items, any entities that can successfully be collected 
				should be reported.";
			type entity-status;
		}

		list message {
			description "The abstract item element specifies an optional message element that is used to pass things like error messages during 
				data collection to a tool that will utilize the information.";

			key "message-index";
			uses message;
		}
	}
}
