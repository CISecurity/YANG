module sacm-microsoft-window-server-baseline {
	namespace "http://cisecurity.org/yang/sacm-win-server";
	prefix "sacm-win-server";

	import "ietf-yang-types" {
		prefix "yang";
	}

	organization "Center for Internet Security";
	contact yang@cisecurity.org;
	description "";
	revision 2018-07-24 {
		description 
			"Initial Version; Types, Groupings, and any other constructs common to the collection of SACM-relevant attributes.";
	}


	// Types
	typedef audit-policy-type {
		type enumeration {
			//description "Audit event policy values";
			enum AUDIT_NONE {
				description "The audit type AUDIT_NONE is used to cancel all auditing options for the specified events";
			}
			enum AUDIT_SUCCESS {
				description "The audit type AUDIT_SUCCESS is used to perform audits on all successful occurrences of the 
					specified events when auditing is enabled.";
			}
			enum AUDIT_FAILURE {
				description "The audit type AUDIT_FAILURE is used to perform audits on all unsuccessful occurrences of 
					specified events when auditing is enabled.";
			}
			enum AUDIT_SUCCESS_FAILURE {
				description "The audit type AUDIT_SUCCESS_FAILURE is used to perform audits on all successful and unsuccessful 
					occurrences of the specified events when auditing is enabled.";
			}
		}
	}

	// Groupings
	grouping trustees {
		description "The identification of a trustee on the sytem, uniquely identified by the SID.";

		list trustee {
			key "trustee-sid";

			leaf trustee-sid {
				description "A security identifier (SID) is a unique value of variable length used to identify a trustee. Each account has 
					a unique SID issued by an authority, such as a Windows domain controller, and stored in a security database";
				type string;
			}
			leaf trustee-name {
				description "The account name associated with the given SID";
				type string;
			}
			leaf trustee-domain {
				description "The domain on which the SID is found";
				type string;
			}
		}
	}

	grouping firewall-profile {
		description "";
		leaf enable-firewall {
			description "Select On (recommended) to have Windows Firewall with Advanced Security use the settings for this profile to filter 
				network traffic. If you select Off, Windows Firewall with Advanced Security will not use any of the firewall rules or connection 
				security rules for this profile.";

			type uint32;
		}
		leaf default-inbound-action {
			description "This setting determines the behavior for inbound connections that do not match an inbound firewall rule.";

			type uint32;
		}
		leaf default-outbound-action {
			description "This setting determines the behavior for outbound connections that do not match an outbound firewall rule.  Note that if 
				you set Outbound connections to Block and then deploy the firewall policy by using a GPO, computers that receive the GPO settings 
				cannot receive subsequent Group Policy updates unless you create and deploy an outbound rule that enables Group Policy to work. 
				Predefined rules for Core Networking include outbound rules that enable Group Policy to work. Ensure that these outbound rules are 
				active, and thoroughly test firewall profiles before deploying.";

			type uint32;
		}
		leaf disable-notifications {
			description "Select this option to have Windows Firewall with Advanced Security display notifications to the user when a program is 
			blocked from receiving inbound connections";

			type uint32;
		}
		leaf log-file-path {
			description "Use this option to specify the path and name of the file in which Windows Firewall will write its log information.";
			type string;
		}
		leaf log-file-size-kb {
			description "Use this option to specify the size limit of the file in which Windows Firewall will write its log information.";
			type uint32;
		}
		leaf log-dropped-packets {
			description "Use this option to log when Windows Firewall with Advanced Security discards an inbound packet for any reason. The log 
			records why and when the packet was dropped. Look for entries with the word DROP in the action column of the log.";

			type uint32;
		}
		leaf log-successfull-connections {
			description "Use this option to log when Windows Firewall with Advanced Security allows an inbound connection. The log records why 
			and when the connection was formed. Look for entries with the word ALLOW in the action column of the log.";

			type uint32;
		}
	}

	grouping firewall-public-profile {
		uses firewall-profile;

		leaf allow-local-policy-merge {
			description "This setting controls whether local administrators are allowed to create local firewall rules that apply together with 
				firewall rules configured by Group Policy. Note that when the Apply local firewall rules setting is configured to No, it's recommended 
				to also configure the Display a notification setting to No. Otherwise, users will continue to receive messages that ask if they want 
				to unblock a restricted inbound connection, but the user's response will be ignored.";

			type uint32;
		}
		leaf allow-local-ipsec-policy-merge {
			description "This setting controls whether local administrators are allowed to create connection security rules that apply together with 
			connection security rules configured by Group Policy.";

			type uint32;
		}
	}

	// Containers

	container account-policies {
		description "";

		container password-policy {
			description "";

			leaf password-history-length {
				description "This policy setting determines the number of renewed, unique passwords that have to be 
					associated with a user account before you can reuse an old password. The value for this policy 
					setting must be between 0 and 24 passwords. The default value for Windows Vista is 0 passwords, 
					but the default setting in a domain is 24 passwords. To maintain the effectiveness of this policy 
					setting, use the Minimum password age setting to prevent users from repeatedly changing their password.";

				type uint32;
			}
			leaf maximum-password-age {
				description "This policy setting defines how long a user can use their password before it expires.  Values 
					for this policy setting range from 0 to 999 days. If you set the value to 0, the password will never expire.  
					Because attackers can crack passwords, the more frequently you change the password the less opportunity an 
					attacker has to use a cracked password. However, the lower this value is set, the higher the potential for an 
					increase in calls to help desk support due to users having to change their password or forgetting which password 
					is current.";
				
				type uint32;
			}
			leaf minimum-password-age {
				description "This policy setting determines the number of days that you must use a password before you can change it. 
					The range of values for this policy setting is between 1 and 999 days. (You may also set the value to 0 to allow 
					immediate password changes.) The default value for this setting is 0 days.";
				
				type uint32;
			}
			leaf minimum-password-length {
				description "This policy setting determines the least number of characters that make up a password for a user account. 
					There are many different theories about how to determine the best password length for an organization, but perhaps 
					'pass phrase' is a better term than 'password.' In Microsoft Windows 2000 and newer, pass phrases can be quite long 
					and can include spaces. Therefore, a phrase such as 'I want to drink a $5 milkshake' is a valid pass phrase; it is a 
					considerably stronger password than an 8 or 10 character string of random numbers and letters, and yet is easier to 
					remember. Users must be educated about the proper selection and maintenance of passwords, especially with regard to 
					password length. In enterprise environments, the ideal value for the Minimum password length setting is 14 characters, 
					however you should adjust this value to meet your organization's business requirements.";
				
				type uint32;
			}
			leaf password-must-meet-complexity-requirements {
				description "This policy setting checks all new passwords to ensure that they meet basic requirements for strong passwords.  
					When this policy is enabled, passwords must meet the following minimum requirements: 
					- Not contain the user's account name or parts of the user's full name that exceed two consecutive characters
					- Be at least six characters in length
					- Contain characters from three of the following four categories:
						-- English uppercase characters (A through Z)
						-- English lowercase characters (a through z)
						-- Base 10 digits (0 through 9)
						-- Non-alphabetic characters (for example, !, $, #, %)
						-- A catch-all category of any Unicode character that does not fall under the previous four categories. This fifth 
						   category can be regionally specific.
					Each additional character in a password increases its complexity exponentially. For instance, a seven-character, all 
					lower-case alphabetic password would have 267 (approximately 8 x 109 or 8 billion) possible combinations. At 1,000,000 
					attempts per second (a capability of many password-cracking utilities), it would only take 133 minutes to crack. A seven-character 
					alphabetic password with case sensitivity has 527 combinations. A seven-character case-sensitive alphanumeric password without 
					punctuation has 627 combinations. An eight-character password has 268 (or 2 x 1011) possible combinations. Although this might 
					seem to be a large number, at 1,000,000 attempts per second it would take only 59 hours to try all possible passwords. Remember, 
					these times will significantly increase for passwords that use ALT characters and other special keyboard characters such as '!' or '@'.
					Proper use of the password settings can help make it difficult to mount a brute force attack.";
				
				type boolean;
			}
			leaf store-passwords-using-reversible-encryption {
				description "This policy setting determines whether the operating system stores passwords in a way that uses reversible encryption, 
					which provides support for application protocols that require knowledge of the user's password for authentication purposes. 
					Passwords that are stored with reversible encryption are essentially the same as plaintext versions of the passwords.";

				type boolean;
			}
		}

		container account-lockout-policy {
			description "";

			leaf account-lockout-duration {
				description "This policy setting determines the length of time that must pass before a locked account is unlocked and a user can try 
					to log on again. The setting does this by specifying the number of minutes a locked out account will remain unavailable. If the 
					value for this policy setting is configured to 0, locked out accounts will remain locked out until an administrator manually unlocks 
					them.  Although it might seem like a good idea to configure the value for this policy setting to a high value, such a configuration 
					will likely increase the number of calls that the help desk receives to unlock accounts locked by mistake. Users should be aware of 
					the length of time a lock remains in place, so that they realize they only need to call the help desk if they have an extremely urgent 
					need to regain access to their computer.";

				type uint32;
			}
			leaf account-lockout-threshold {
				description "This policy setting determines the number of failed logon attempts before the account is locked. Setting this policy to 0 does 
					not conform to the benchmark as doing so disables the account lockout threshold.";
				
				type uint32;
			}
			leaf reset-account-lockout-counter-after {
				description "This policy setting determines the length of time before the Account lockout threshold resets to zero. The default value for 
					this policy setting is Not Defined. If the Account lockout threshold is defined, this reset time must be less than or equal to the value 
					for the Account lockout duration setting.  If you leave this policy setting at its default value or configure the value to an interval 
					that is too long, your environment could be vulnerable to a DoS attack. An attacker could maliciously perform a number of failed logon 
					attempts on all users in the organization, which will lock out their accounts. If no policy were determined to reset the account lockout, 
					it would be a manual task for administrators. Conversely, if a reasonable time value is configured for this policy setting, users would be 
					locked out for a set period until all of the accounts are unlocked automatically.";
				
				type uint32;
			}
		}
	}

	container local-policies {
		description "";

		container audit-policy {}
		container user-rights-assignment {
			description "";
			container access-credential-manager-as-a-trusted-caller {
				description "";
				uses trustees;
			}
			container access-this-computer-from-the-network {
				description "";
				uses trustees;
			}
			container act-as-part-of-the-operating-system {
				description "";
				uses trustees;
			}
			container add-workstations-to-the-domain {
				description "";
				uses trustees;
			}
			container adjust-memory-quotas-for-a-process {
				description "";
				uses trustees;
			}
			container allow-log-on-locally {
				description "";
				uses trustees;
			}
			container allow-log-on-through-remote-desktop-services {
				description "";
				uses trustees;
			}
			container backup-files-and-directories {
				description "";
				uses trustees;
			}
			container change-the-system-time {
				description "";
				uses trustees;
			}
			container change-the-time-zone {
				description "";
				uses trustees;
			}
			container create-a-pagefile {
				description "";
				uses trustees;
			}
			container create-a-token-object {
				description "";
				uses trustees;
			}
			container create-global-objects {
				description "";
				uses trustees;
			}
			container create-permanent-shared-objects {
				description "";
				uses trustees;
			}
			container create-symbolic-links {
				description "";
				uses trustees;
			}
			container debug-programs {
				description "";
				uses trustees;
			}
			container deny-access-to-this-computer-from-the-network {
				description "";
				uses trustees;
			}
			container deny-log-on-as-a-batch-job {
				description "";
				uses trustees;
			}
			container deny-log-on-as-a-service {
				description "";
				uses trustees;
			}
			container deny-log-on-locally {
				description "";
				uses trustees;
			}
			container deny-log-on-through-remote-desktop-services {
				description "";
				uses trustees;
			}
			container enable-computer-and-user-accounts-trusted-for-delegation {
				description "";
				uses trustees;
			}
			container force-shutdown-from-a-remote-system {
				description "";
				uses trustees;
			}
			container generate-security-audits {
				description "";
				uses trustees;
			}
			container impersonate-a-client-after-authentication {
				description "";
				uses trustees;
			}
			container increase-scheduling-priority {
				description "";
				uses trustees;
			}
			container load-and-unload-device-drivers {
				description "";
				uses trustees;
			}
			container lock-pages-in-memory {
				description "";
				uses trustees;
			}
			container log-on-as-a-batch-job {
				description "";
				uses trustees;
			}
			container manage-auditing-and-security-log {
				description "";
				uses trustees;
			}
			container modify-an-object-label {
				description "";
				uses trustees;
			}
			container modify-firmware-environment-values {
				description "";
				uses trustees;
			}
			container perform-volume-maintenance-tasks {
				description "";
				uses trustees;
			}
			container profile-single-process {
				description "";
				uses trustees;
			}
			container profile-system-performance {
				description "";
				uses trustees;
			}
			container replace-a-process-level-token {
				description "";
				uses trustees;
			}
			container restore-files-and-directories {
				description "";
				uses trustees;
			}
			container shutdown-the-system {
				description "";
				uses trustees;
			}
			container synchronize-directory-service-data {
				description "";
				uses trustees;
			}
			container take-ownership-of-files-or-other-objects {
				description "";
				uses trustees;
			}
		}

		container security-options {
			description "This section contains configuration items for security options.";
			
			container accounts {
				description "This section contains configuration items related to default accounts.";
				leaf administrator-account-enabled {
					description "This policy setting enables or disables the Administrator account during normal operation. When a computer is 
						booted into safe mode, the Administrator account is always enabled, regardless of how this setting is configured. Note 
						that this setting will have no impact when applied to the Domain Controllers organizational unit via group policy because 
						Domain Controllers have no local account database. It can be configured at the domain level via group policy, similar to 
						account lockout and password policy settings.

						The Windows Administrator account SID matches the regular expression '^S\-1\-5\-21\-\d+\-\d+\-\d+\-500$'";

					type boolean;
				}
				leaf block-microsoft-accounts {
					description "This policy setting prevents users from adding new Microsoft accounts on this computer.

						Registry Key: HKEY_LOCAL_MACHINE\SOFTWARE\Microsoft\Windows\CurrentVersion\Policies\System
						Registry Name: NoConnectedUser";

					type uint32;
				}
				leaf guest-account-enabled {
					description "This policy setting determines whether the Guest account is enabled or disabled. The Guest account allows unauthenticated 
						network users to gain access to the system.  Note that this setting will have no impact when applied to the Domain Controllers 
						organizational unit via group policy because Domain Controllers have no local account database. It can be configured at the domain 
						level via group policy, similar to account lockout and password policy settings.

						The Windows Guest account SID matches the regular expression '^S\-1\-5\-21\-\d+\-\d+\-\d+\-501$'";

					type boolean;
				}
				leaf limit-local-account-use-of-blank-passwords {
					description "This policy setting determines whether local accounts that are not password protected can be used to log on from locations 
						other than the physical computer console. If you enable this policy setting, local accounts that have blank passwords will not be able 
						to log on to the network from remote client computers. Such accounts will only be able to log on at the keyboard of the computer.

						Registry Key: HKEY_LOCAL_MACHINE\SYSTEM\CurrentControlSet\Control\Lsa
						Registry Name: LimitBlankPasswordUse";

					type uint32;
				}
				leaf administrator-account-name {
					description "The built-in local administrator account is a well-known account name that attackers will target. It is recommended to choose 
						another name for this account, and to avoid names that denote administrative or elevated access accounts. Be sure to also change the 
						default description for the local administrator (through the Computer Management console). On Domain Controllers, since they do not have 
						their own local accounts, this rule refers to the built-in Administrator account that was established when the domain was first created.";

					type string;
				}
				leaf guest-account-name {
					description "The built-in local guest account is another well-known name to attackers. It is recommended to rename this account to something 
						that does not indicate its purpose. Even if you disable this account, which is recommended, ensure that you rename it for added security. 
						On Domain Controllers, since they do not have their own local accounts, this rule refers to the built-in Guest account that was established 
						when the domain was first created.";

					type string;
				}
			}
			container audit {
				description "";
				leaf sce-no-apply-legacy-audit-policy {
					description "This policy setting allows administrators to enable the more precise auditing capabilities present in 
						Windows Vista. The Audit Policy settings available in Windows Server 2003 Active Directory do not yet contain 
						settings for managing the new auditing subcategories. To properly apply the auditing policies prescribed in this 
						baseline, the Audit: Force audit policy subcategory settings (Windows Vista or later) to override audit policy 
						category settings setting needs to be configured to Enabled.

						Registry Key: HKEY_LOCAL_MACHINE\SYSTEM\CurrentControlSet\Control\Lsa
						Registry Name: SCENoApplyLegacyAuditPolicy";

					type uint32;
				}
				leaf crash-on-audit-fail {
					description "This policy setting determines whether the system shuts down if it is unable to log Security events. It is 
						a requirement for Trusted Computer System Evaluation Criteria (TCSEC)-C2 and Common Criteria certification to prevent 
						auditable events from occurring if the audit system is unable to log them. Microsoft has chosen to meet this requirement 
						by halting the system and displaying a stop message if the auditing system experiences a failure. When this policy setting 
						is enabled, the system will be shut down if a security audit cannot be logged for any reason. If the Audit: Shut down system 
						immediately if unable to log security audits setting is enabled, unplanned system failures can occur. The administrative 
						burden can be significant, especially if you also configure the Retention method for the Security log to Do not overwrite 
						events (clear log manually). This configuration causes a repudiation threat (a backup operator could deny that they backed 
						up or restored data) to become a denial of service (DoS) vulnerability, because a server could be forced to shut down if it 
						is overwhelmed with logon events and other security events that are written to the Security log. Also, because the shutdown 
						is not graceful, it is possible that irreparable damage to the operating system, applications, or data could result. Although 
						the NTFS file system guarantees its integrity when an ungraceful computer shutdown occurs, it cannot guarantee that every data 
						file for every application will still be in a usable form when the computer restarts.

						Registry Key: HKEY_LOCAL_MACHINE\SYSTEM\CurrentControlSet\Control\Lsa
						Registry Name: CrashOnAuditFail";

					type uint32;
				}
			}
			container dcom {}
			container devices {
				description "This section contains configuration items related to managing devices.";
				leaf allocate-dasd {
					description "This policy setting determines who is allowed to format and eject removable NTFS media. You can use this policy setting 
						to prevent unauthorized users from removing data on one computer to access it on another computer on which they have local 
						administrator privileges

						Registry Key: HKEY_LOCAL_MACHINE\SOFTWARE\Microsoft\Windows NT\CurrentVersion\Winlogon
						Registry Name: AllocateDASD";

					type uint32;
				}
				leaf add-printer-drivers {
					description "For a computer to print to a shared printer, the driver for that shared printer must be installed on the local computer. 
						This security setting determines who is allowed to install a printer driver as part of connecting to a shared printer.

						Registry Key: HKEY_LOCAL_MACHINE\SYSTEM\CurrentControlSet\Control\Print\Providers\LanMan Print Services\Servers
						Registry Name: AddPrinterDrivers";

					type uint32;
				}
			}
			container domain-controller {
				description "This section contains configuration items related to Domain Controllers.";

				leaf submit-control {
					description "This policy setting determines whether members of the Server Operators group are allowed to submit jobs by means of 
						the AT schedule facility. The impact of this policy setting configuration should be small for most organizations. Users, 
						including those in the Server Operators group, will still be able to create jobs by means of the Task Scheduler Wizard, but 
						those jobs will run in the context of the account with which the user authenticates when they set up the job.

						Note: An AT Service Account can be modified to select a different account rather than the LOCAL SYSTEM account. To change the 
						account, open System Tools, click Scheduled Tasks, and then click Accessories folder. Then click AT Service Account on the Advanced menu.

						Registry Key: HKEY_LOCAL_MACHINE\SYSTEM\CurrentControlSet\Control\Lsa
						Registry Name: SubmitControl";

					type uint32;
				}
				leaf ldap-server-integrity {
					description "This policy setting determines whether the Lightweight Directory Access Protocol (LDAP) server requires LDAP 
						clients to negotiate data signing.
						
						Note: Domain member computers must have Network security: LDAP signing requirements (Rule 2.3.11.8) set to Negotiate signing 
						or higher. If not, they will fail to authenticate once the above Require signing value is configured on the Domain Controllers. 
						Fortunately, Negotiate signing is the default in the client configuration.

						Note #2: This policy setting does not have any impact on LDAP simple bind (ldap_simple_bind) or LDAP simple bind through SSL 
						(ldap_simple_bind_s). No Microsoft LDAP clients that are shipped with Windows XP Professional use LDAP simple bind or LDAP 
						simple bind through SSL to talk to a Domain Controller.

						Note #3: Before enabling this setting, you should first ensure that there are no clients (including server-based applications) 
						that are configured to authenticate with Active Directory via unsigned LDAP, because changing this setting will break those 
						applications. Such applications should first be reconfigured to use signed LDAP, Secure LDAP (LDAPS), or IPsec-protected connections. 
						For more information on how to identify whether your DCs are being accessed via unsigned LDAP (and where those accesses are 
						coming from), see this Microsoft TechNet blog article: Identifying Clear Text LDAP binds to your DC’s – Practical Windows Security

						Registry Key: HKEY_LOCAL_MACHINE\SYSTEM\CurrentControlSet\Services\NTDS\Parameters
						Registry Name: LDAPServerIntegrity";
					
					type uint32;
				}
				leaf refuse-password-change {
					description "This security setting determines whether Domain Controllers will refuse requests from member computers to change 
						computer account passwords.

						Registry Key: HKEY_LOCAL_MACHINE\SYSTEM\CurrentControlSet\Services\Netlogon\Parameters
						Registry Name: RefusePasswordChange";
					type uint32;
				}
			}
			container domain-member {
				description "";
				leaf require-sign-or-seal {
					description "This policy setting determines whether all secure channel traffic that is initiated by the domain member must 
						be signed or encrypted.

						Registry Key: HKEY_LOCAL_MACHINE\SYSTEM\CurrentControlSet\Services\Netlogon\Parameters
						Registry Name: RequireSignOrSeal";
					type uint32;
				}
				leaf seal-secure-channel {
					description "This policy setting determines whether a domain member should attempt to negotiate encryption for all secure 
						channel traffic that it initiates.

						Registry Key: HKEY_LOCAL_MACHINE\SYSTEM\CurrentControlSet\Services\Netlogon\Parameters
						Registry Name: SealSecureChannel";
					type uint32;
				}
				leaf sign-secure-channel {
					description "This policy setting determines whether a domain member should attempt to negotiate whether all secure channel 
						traffic that it initiates must be digitally signed. Digital signatures protect the traffic from being modified by anyone 
						who captures the data as it traverses the network.

						Registry Key: HKEY_LOCAL_MACHINE\SYSTEM\CurrentControlSet\Services\Netlogon\Parameters
						Registry Name: SignSecureChannel";
					type uint32;
				}
				leaf disable-password-change {
					description "This policy setting determines whether a domain member can periodically change its computer account password. 
						Computers that cannot automatically change their account passwords are potentially vulnerable, because an attacker might 
						be able to determine the password for the system's domain account.

						Registry Key: HKEY_LOCAL_MACHINE\SYSTEM\CurrentControlSet\Services\Netlogon\Parameters
						Registry Name: DisablePasswordChange";
					type uint32;
				}
				leaf machine-account-maximum-password-age {
					description "This policy setting determines the maximum allowable age for a computer account password. By default, domain 
						members automatically change their domain passwords every 30 days.

						Registry Key: HKEY_LOCAL_MACHINE\System\CurrentControlSet\Services\Netlogon\Parameters
						Registry Name: MaximumPasswordAge";
					type uint32;
				}
				leaf require-strong-session-key {
					description "When this policy setting is enabled, a secure channel can only be established with Domain Controllers that 
						are capable of encrypting secure channel data with a strong (128-bit) session key. To enable this policy setting, all 
						Domain Controllers in the domain must be able to encrypt secure channel data with a strong key, which means all Domain 
						Controllers must be running Microsoft Windows 2000 or newer.

						Registry Key: HKEY_LOCAL_MACHINE\SYSTEM\CurrentControlSet\Services\Netlogon\Parameters
						Registry Name: RequireStrongKey";
					type uint32;
				}
			}
			container interactive-logon {
				description "This section contains recommendations related to interactive logons.";
				leaf do-not-display-last-username {
					description "This policy setting determines whether the account name of the last user to log on to the client computers 
						in your organization will be displayed in each computer's respective Windows logon screen. Enable this policy setting 
						to prevent intruders from collecting account names visually from the screens of desktop or laptop computers in your 
						organization.

						Registry Key: HKEY_LOCAL_MACHINE\SOFTWARE\Microsoft\Windows\CurrentVersion\Policies\System
						Registry Name: DontDisplayLastUserName";
					type uint32;
				}
				leaf do-not-require-ctrl-alt-del {
					description "";
					type ;
				}
				leaf machine-inactivity-limit {
					description "";
					type ;
				}
				leaf message-text-for-users-attempting-to-log-on {
					description "";
					type ;
				}
				leaf message-title-for-users-attempting-to-log-on {
					description "";
					type ;
				}
				leaf number-of-previous-logons-to-cache {
					description "";
					type ;
				}
				leaf prompt-user-to-change-password-before-expiration {
					description "";
					type ;
				}
				leaf require-domain-controller-authentication-to-unlock-workstation {
					description "";
					type ;
				}
				leaf smart-card-removal-behavior {
					description "";
					type ;
				}
			}
			container microsoft-network-client {
				description "";
				leaf digitally-sign-communications-always {
					description "";
					type ;
				}
				leaf digitally-sign-communications-if-server-agrees {
					description "";
					type ;
				}
				leaf send-unencrypted-password-to-third-party-smb-servers {
					description "";
					type ;
				}
			}
			container microsoft-network-server {
				description "";
				leaf amount-of-idle-time-required-before-suspending-session {
					description "";
					type ;
				}
				leaf digitally-sign-communications-always {
					description "";
					type ;
				}
				leaf digitally-sign-communications-if-client-agrees {
					description "";
					type ;
				}
				leaf disconnect-clients-when-logon-hours-expire {
					description "";
					type ;
				}
				leaf server-spn-target-name-validation-level {
					description "";
					type ;
				}
			}
			container network-access {
				description "";
				leaf allow-anonymous-sid-name-translation {
					description "";
					type ;
				}
				leaf do-not-allow-anonymous-enumeration-of-sam-accounts {
					description "";
					type ;
				}
				leaf do-not-allow-anonymous-enumeration-of-sam-accounts-and-shares {
					description "";
					type ;
				}
				leaf do-not-allow-storage-of-passwords-and-credentials-for-network-authentication {
					description "";
					type ;
				}
				leaf let-everyone-permissions-apply-to-anonymous-users {
					description "";
					type ;
				}
				leaf named-pipes-that-can-be-accessed-anonymously {
					description "";
					type ;
				}
				leaf remotely-accessible-registry-paths {
					description "";
					type ;
				}
				leaf remotely-accessible-registry-paths-and-subpaths {
					description "";
					type ;
				}
				leaf restrict-anonymous-access-to-named-pipes-and-shares {
					description "";
					type ;
				}
				leaf restrict-clients-allowed-to-make-remote-calls-to-sam {
					description "";
					type ;
				}
				leaf shares-that-can-be-accessed-anonymously {
					description "";
					type ;
				}
				leaf sharing-and-security-model-for-local-accounts {
					description "";
					type ;
				}
			}
			container network-security {
				description "";
				leaf allow-local-system-to-use-computer-identity-for-ntlm {
					description "";
					type ;
				}
				leaf allow-local-system-null-session-fallback {
					description "";
					type ;
				}
				leaf allow-pku2u-authentication-requests {
					description "";
					type ;
				}
				leaf configure-encryption-types-allowed-for-kerberos {
					description "";
					type ;
				}
				leaf do-not-store-lan-manager-hash-value-on-next-password-change {
					description "";
					type ;
				}
				leaf force-logoff-when-logon-hours-expire {
					description "";
					type ;
				}
				leaf lan-manager-authentication-level {
					description "";
					type ;
				}
				leaf ldap-client-signing-requirements {
					description "";
					type ;
				}
				leaf minimum-session-security-for-ntlm-ssp-based-clients {
					description "";
					type ;
				}
				leaf minimum-session-security-for-ntlm-ssp-based-servers {
					description "";
					type ;
				}
			}
			container recovery-console {}
			container shutdown {
				description "";
				leaf allow-system-shutdown-without-having-to-log-on {
					description "";
					type ;
				}
			}
			container system-cryptograhy {}
			container system-objects {
				description "";
				leaf require-case-insensitivity-for-non-windows-subsystems {
					description "";
					type ;
				}
				leaf strengthen-default-permissions-of-internal-system-objects {
					description "";
					type ;
				}
			}
			container system-settings {
				description "";
				leaf optional-subsystems {
					description "";
					type ;
				}
			}
			container user-account-control {
				description "";
				leaf admin-approval-mode-for-builtin-administrator-account {
					description "";
					type ;
				}
				leaf allow-uiaccess-applications-to-prompt-for-elevation-without-secure-desktop {
					description "";
					type ;
				}
				leaf elevation-prompt-behavior-for-administrators-admin-approval-mode {
					description "";
					type ;
				}
				leaf elevation-prompt-behavior-for-standard-users {
					description "";
					type ;
				}
				leaf only-elevate-uiaccess-applications-installed-in-secure-locations {
					description "";
					type ;
				}
				leaf run-all-administrators-in-admin-approval-mode {
					description "";
					type ;
				}
				leaf switch-to-secure-desktop-when-prompting-for-elevation {
					description "";
					type ;
				}
				leaf virtualize-file-and-registry-write-failures-to-per-user-locations {
					description "";
					type ;
				}
			}
		}
	}

	container event-log {}
	container restricted-groups {}
	container system-services {}
	container registry {}
	container file-system {}
	container wired-network-ieee-802-3-policies {}
	container windows-firewall-with-advanced-security {
		description "";
		container domain-profile {
			description "This section contains configuration items for the Domain Profile of the Windows Firewall.";
			
			uses firewall-profile;
		}
		container private-profile {
			description "This section contains configuration items for the Private Profile of the Windows Firewall.";
			uses firewall-profile;
		}
		container public-profile {
			description "This section contains configuration items for the Public Profile of the Windows Firewall.";

			uses firewall-public-profile;
		}
	}
	container network-list-manager-policies {}
	container wireless-network-ieee-802-11-policies {}
	container public-key-policies {}
	container software-restriction-policies {}
	container network-access-protection-client-configuration {}
	container application-control-policies {}
	container ip-security-policies {}

container advanced-audit-policy-configuration {
	description "";
	container account-logon {
		description "";
		leaf audit-credential-validation {
			description "";

			type audit-policy-type;
		}
	}
	container account-management {
		description "";
		leaf audit-application-group-management {
			description "";

			type audit-policy-type;
		}
		leaf audit-computer-account-management {
			description "";

			type audit-policy-type;
		}
		leaf audit-distribution-group-management {
			description "";

			type audit-policy-type;
		}
		leaf audit-other-account-management-events {
			description "";

			type audit-policy-type;
		}
		leaf audit-security-group-management {
			description "";

			type audit-policy-type;
		}
		leaf audit-user-account-management {
			description "";

			type audit-policy-type;
		}
	}
	container detailed-tracking {
		description "";
		leaf audit-pnp-activity {
			description "";

			type audit-policy-type;
		}
		leaf audit-process-creation {
			description "";

			type audit-policy-type;
		}
	}
	container ds-access {
		description "";
		leaf audit-directory-service-access {
			description "";

			type audit-policy-type;
		}
		leaf audit-directory-service-changes {
			description "";

			type audit-policy-type;
		}
	}
	container logon-logoff {
		description "";
		leaf audit-account-lockout {
			description "";

			type audit-policy-type;
		}
		leaf audit-group-membership {
			description "";

			type audit-policy-type;
		}
		leaf audit-logoff {
			description "";

			type audit-policy-type;
		}
		leaf audit-logon {
			description "";

			type audit-policy-type;
		}
		leaf audit-other-logon-logoff-events {
			description "";

			type audit-policy-type;
		}
		leaf audit-special-logon {
			description "";

			type audit-policy-type;
		}
	}
	container object-access {
		description "";
		leaf audit-other-object-access-events {
			description "";

			type audit-policy-type;
		}
		leaf audit-removable-storage {
			description "";

			type audit-policy-type;
		}
	}
	container policy-change {
		description "";
		leaf audit-policy-change {
			description "";

			type audit-policy-type;
		}
		leaf audit-authentication-policy-change {
			description "";

			type audit-policy-type;
		}
		leaf audit-authorization-policy-change {
			description "";

			type audit-policy-type;
		}
	}
	container privilege-use {
		description "";
		leaf audit-sensitive-privilege-use {
			description "";

			type audit-policy-type;
		}
	}
	container system {
		description "";
		leaf audit-ipsec-driver {
			description "";

			type audit-policy-type;
		}
		leaf audit-other-system-events {
			description "";

			type audit-policy-type;
		}
		leaf audit-security-state-change {
			description "";

			type audit-policy-type;
		}
		leaf audit-security-system-extension {
			description "";

			type audit-policy-type;
		}
		leaf audit-system-integrity {
			description "";

			type audit-policy-type;
		}
	}
}

container administrative-templates-computer
	container control-panel
		container personalization
			leaf prevent-enabling-lock-screen-camera
			leaf prevent-enabling-lock-screen-slideshow
		container regional-and-language-options
			container handwriting-personalization {}
			leaf allow-input-personlization
		leaf allow-online-tips
	container laps
		leaf ensure-laps-admpwd-gpo-extension
		leaf do-not-allow-password-expiration-time-longer-than-required-by-policy
		leaf enable-local-admin-password-management
		leaf password-complexity
		leaf password-length
		leaf password-age-days
	container ms-security-guide
		leaf apply-uac-restrictions-to-local-accounts-on-network-logons
		leaf configure-smb-v1-client
		leaf configure-smb-v1-client-driver
		leaf configure-smb-v1-server
		leaf enable-structured-exception-handling-overwrite-protection-sehop
		leaf turn-on-windows-defender-protection-against-potentially-unwanted-applications
		leaf wdigest-authentication
	container mss-legacy
		leaf mss-auto-admin-logon
		leaf mss-disable-ip-source-routing-ipv6
		leaf mss-disable-ip-source-routign
		leaf mss-enable-icmp-redirect
		leaf mss-keep-alive-time
		leaf mss-non-name-release-on-demand
		leaf mss-perform-router-discovery
		leaf mss-safe-dll-search-mode
		leaf mss-screen-saver-grace-period
		leaf mss-tcp-max-data-retransmissions-ipv6
		leaf mss-tcp-max-data-retransmissions
		leaf mss-warning-level
	container network
		container background-intelligent-transfer-service {}
		container branch-cache {}
		container direct-access-client-experience-settings {}
		container dns-client
			leaf set-netbios-node-type-to-p-node
			leaf turn-off-multicast-name-resolution
		container fonts
			leaf enable-font-providers
		container hostpot-authentication {}
		container lanman-server {}
		container lanman-workstation
			leaf enable-insecure-guest-logons
		container link-layer-topology-discovery
			leaf turn-on-mapper-io-lltdio-driver
			leaf turn-on-responder-rspndr-driver
		container microsoft-peer-to-peer-networking-services
			container peer-name-resolution-protocol {}
			leaf turn-off-microsoft-peer-to-peer-networking-services
		container network-connections
			container windows-defender-firewall {}
			leaf prohibit-installation-and-configuration-of-network-bridge-on-dns-domain-network
			leaf prohibit-use-of-internet-connection-sharing-on-dns-domain-network
			leaf require-domain-users-to-elevate-when-setting-network-location
		container network-connectivity-status-indicator {}
		container network-isolation {}
		container network-provider
			leaf hardened-unc-paths-netlogon-sysvol-shares
		container offline-files {}
		container qos-packet-scheduler {}
		container snmp {}
		container ssl-configuration-settings {}
		container tcpip-settings
			container ipv6-transition-technologies {}
			container parameters
				leaf disable-ipv6
		container windows-connect-now
			leaf configuration-of-wireless-settings-using-windows-connect-now
			leaf prohibit-access-of-windows-connect-now-wizards
		container windows-connection-manager
			leaf minimize-number-of-simultaneous-connections-to-internet-or-windows-domain
			leaf prohibit-connection-to-non-domain-networks
	container printers {}
	container start-menu-and-taskbar {}
	container system
		container access-denied-assistance {}
		container app-v {}
		container audit-process-creation
			leaf include-command-line-in-process-creation-events
		container credentials-delegation
			leaf remote-host-allows-delegation-of-non-exportable-credentials
		container device-guard
			leaf turn-on-virtualization-based-security
			leaf vbs-platform-security-level
			leaf vbs-virtualization-based-protection-of-code-integrity
			leaf vbs-require-uefi-memory-attributes-table
			leaf vbs-credential-guard-configuration
		container device-health-attestation-service {}
		container device-installation
			container device-installation-restrictions {}
			leaf allow-remote-access-to-plug-and-play-interface
		container device-redirection {}
		container disk-nv-cache {}
		container disk-quotas {}
		container display {}
		container distributed-com {}
		container driver-instalation {}
		container early-launch-anti-malware
			leaf boot-start-driver-initialization-policy
		container enhanced-storage-access {}
		container file-classification-infrastructure {}
		container file-share-shadow-copy-agent {}
		container file-share-shadow-copy-provider {}
		container filesystem {}
		container folder-redirection {}
		container group-policy {
			container logging-and-tracing {}
			leaf registry-policy-processing-do-not-apply-during-periodic-background-processing
			leaf registry-policy-processing-process-even-if-gpos-have-not-changed
			leaf continue-experiences-on-this-device
			leaf turn-off-background-refresh-of-group-policy
		}
		container internet-communication-management
			container internet-communication-settings
				leaf turn-off-downloading-print-drivers-over-http
				leaf turn-off-handwriting-personalization-data-sharing
				leaf turn-off-handwriting-recognition-error-reporting
				leaf turn-off-internet-connection-wizard-if-url-microsoft-dot-com
				leaf turn-off-internet-download-for-web-publishing-online-ordering
				leaf turn-off-internet-file-association-service
				leaf turn-off-printing-over-http
				leaf turn-off-registration-if-url-microsoft-dot-com
				leaf turn-off-search-companion-content-file-updates
				leaf turn-off-order-prints-picture-task
				leaf turn-off-publish-to-web-task-files-folders
				leaf turn-off-windows-messenger-customer-experience-improvement-program
				leaf turn-off-windows-customer-experience-improvement-program
				leaf turn-off-windows-error-reporting
		container iscsi {}
		container kdc {}
		container kerberos
			leaf support-device-authentication-using-certificate
		container locale-services
			leaf disallow-copying-user-input-methods-to-system-account-for-sign-in
		container logon
			leaf always-use-classic-logon
			leaf block-user-showing-account-details-on-sign-in
			leaf do-not-display-network-selection-ui
			leaf do-not-enumerate-connected-users-on-domain-joined-computers
			leaf turn-off-app-notifications-on-lock-screen
			leaf turn-off-picture-password-sign-in
			leaf turn-on-convenience-pin-sign-in
		container mitigation-options
			leaf untrusted-font-blocking
		container net-logon {}
		container os-policies {}
		container performance-control-panel {}
		container pin-complexity {}
		container power-management
			container button-settings {}
			container energy-saver-settings {}
			container hard-disk-settings {}
			container notification-settings {}
			container power-throttling-settings {}
			container sleep-settings
				leaf allow-network-connectivity-connected-standby-battery
				leaf allow-network-connectivity-connected-standby-plugged-in
				leaf require-password-when-computer-wakes-battery
				leaf require-password-when-computer-wakes-plugged-in
		container recovery {}
		container remote-assistance
			leaf configure-offer-remote-assistance
			leaf configure-solicited-remote-assistance
		container remote-procedure-call
			leaf enable-rpc-endpoint-mapper-client-authentication
			leaf restrict-unauthenticated-rpc-clients
		container removable-storage-access {}
		container scripts {}
		container server-maager {}
		container shutdown {}
		container storage-health {}
		container system-restore {}
		container troubleshooting-and-diagnostics
			container application-compatibility-diagnostics {}
			container corrupted-file-recovery {}
			container disk-diagnostic {}
			container fault-tolerant-heap {}
			container microsoft-support-diagnostic-tool
				leaf turn-on-msdt-interactive-communication-with-support-provider
			container msi-corrupted-file-recovery {}
			container scheduled-maintenance {}
			container scripted-diagnostics {}
			container windows-boot-performance-diagnostics {}
			container windows-memory-leak-diagnosis {}
			container windows-performance-perf-track
				leaf enable-disable-perf-track
		container trusted-platform-module-services {}
		container user-profiles
			leaf turn-off-advertising-id
		container windows-file-protection {}
		container windows-hot-start {}
		container windows-time-service
			container time-providers
				leaf enable-windows-ntp-client
				leaf enable-windows-ntp-server
	container windows-components
		container active-directory-federation-services {}
		container activex-installer-service {}
		container add-features-to-windows-anytime-upgrade {}
		container app-package-deployment
			leaf allow-windows-app-to-share-application-data-between-users
		container app-privacy {}
		container app-runtime
			leaf allow-microsoft-accounts-to-be-optional
		container application-compatibility {}
		container auto-play-policies
			leaf disallow-autoplay-for-non-volume-devices
			leaf auto-run-default-behavior
			leaf turn-off-auto-play
		container backup {}
		container biometrics
			container facial-features
				leaf configure-enhanced-anti-spoofing
		container bitlocker-drive-encryption {}
		container camera
			leaf allow-use-of-camera
		container cloud-content
			leaf turn-off-microsoft-consumer-experiences
		container connect
			leaf require-pin-for-pairing
		container credential-user-interface
			leaf do-not-display-password-reveal-button
			leaf enumerate-administrator-accounts-on-elevation
		container data-collection-and-preview-builds
			leaf allow-telemetry
			leaf configure-authenticated-proxy-connected-user-experience-telemetry
			leaf disable-pre-release-features-settings
			leaf do-not-show-feedback-notifications
			leaf toggle-user-control-over-insider-builds
		container delivery-optimization {}
		container desktop-gadgets
			leaf turn-off-desktop-gadgets
			leaf turn-off-user-installed-desktop-gadgets
		container desktop-window-manager {}
		container device-and-driver-compatibility {}
		container device-registration-workplace-join {}
		container digital-locker {}
		container edge-ui {}
		container emet
			leaf installed-emet-version
			leaf default-action-mitigation-settings
			leaf default-protections-internet-explorer
			leaf default-protections-popular-software
			leaf default-protections-recommended-software
			leaf system-aslr
			leaf system-dep
			leaf system-sehop
		container event-forwarding {}
		container event-log-service
			container application
				leaf control-event-log-behavior-maximum-log-size
				leaf maximum-log-file-size-kb
			container security
				leaf control-event-log-behavior-maximum-log-size
				leaf maximum-log-file-size-kb
			container setup
				leaf control-event-log-behavior-maximum-log-size
				leaf maximum-log-file-size-kb
			container system
				leaf control-event-log-behavior-maximum-log-size
				leaf maximum-log-file-size-kb
		container event-logging {}
		container event-viewer {}
		container family-safety-parental-controls {}
		container file-explorer-windows-explorer
			container previous-versions {}
			leaf turn-off-data-execution-prevention
			leaf turn-off-heap-termination-on-corruption
			leaf turn-off-shell-protocol-protected-mode
		container file-history {}
		container find-my-device {}
		container game-explorer {}
		container handwriting {}
		container home-group {}
		container import-video {}
		container internet-explorer {}
		container internet-information-services {}
		container location-and-sensors {}
			container windows-location-provider
				leaf turn-off-windows-location-provider
			leaf turn-off-location
		container maintenance-scheduler {}
		container maps {}
		container mdm {}
		container messaging
			leaf allow-message-service-cloud-sync
		container microsoft-account
			leaf block-all-consumer-microsoft-account-user-authentication
		container microsoft-edge {}
		container microsoft-fido-authentication {}
		container microsoft-secondary-authentication-factor {}
		container microsoft-user-experience-virtualization {}
		container net-meeting {}
		container network-access-protection {}
		container network-projector {}
		container one-drive
			leaf prevent-usage-one-drive-file-storage
			leaf prevent-usage-one-drive-file-storage-windows-8-1
		container online-assistance {}
		container password-syncronization {}
		container portable-operating-system {}
		container presentation-settings {}
		container push-to-install {}
		container remote-desktop-services {}
			container rd-licensing {}
			container remote-desktop-connection-client
				container remote-fx-usb-device-redirection {}
				leaf do-not-allow-password-saving
			container remote-desktop-session-host
				container application-compatibility {}
				container connections
					leaf restrict-remote-desktop-services-single-session
				container device-and-resource-redirection
					leaf do-not-allow-com-port-redirection
					leaf do-not-allow-drive-redirection
					leaf do-not-allow-lpt-port-redirection
					leaf do-not-allow-supported-plug-and-play-device-redirection
				container licensing {}
				container printer-redirection {}
				container profiles {}
				container rd-connection-broker {}
				container remote-session-environment {}
				container security
					leaf always-prompt-for-password-upon-connection
					leaf require-secure-rpc-communication
					leaf set-client-connection-encryption-level
				container session-time-limits
					leaf set-time-limit-active-idle-remote-desktop-services-sessions
					leaf set-time-limit-disconnected-sessions
				container temporary-folders
					leaf do-not-delete-temp-folders-upon-exit
					leaf do-not-use-temporary-folders-per-session
		container rss-feeds
			leaf prevent-downloading-of-enclosures
		container search
			container ocr
			leaf allow-indexing-of-encrypted-files
			leaf set-information-shared-in-search
			leaf allow-cloud-search
		container security-center {}
		container server-for-nis {}
		container shutdown-options {}
		container smart-card {}
		container software-protection-platform
			leaf turn-off-kms-client-online-avs-validation
		container sound-recorder {}
		container speech {}
		container store {}
		container sync-your-settings {}
		container tablet-pc {}
		container task-scheduler {}
		container text-input {}
		container windows-calendar {}
		container windows-color-system {}
		container windows-customer-experience-improvement-program {}
		container windows-defender-antivirus
			container client-interface {}
			container exclusions {}
			container maps
				leaf configure-local-setting-override-for-maps-reporting
				leaf join-microsoft-maps
			container mp-engine {}
			container network-inspection-system {}
			container quarantine {}
			container real-time-protection
				leaf turn-on-behavior-monitoring
			container remediation {}
			container reporting
				leaf configure-watson-events
			container scan
				leaf scan-removable-drives
				leaf turn-on-email-scanning
			container signature-updates {}
			container threats {}
			container windows-defender-exploit-guard
				container attack-surface-reduction
					leaf configure-attack-surface-reduction-rules
					leaf configure-attack-surface-reduction-rules-asr-rule-state
				container controlled-folder-access {}
				container network-protection
					leaf prevent-users-apps-accessing-dangerous-websites
		container windows-defender-application-guard {}
		container windows-defender-exploit-guard
			container attack-surface-reduction {}
			container controlled-folder-access {}
			container network-protection
				leaf prevent-users-apps-accessing-dangerous-websites
		container windows-defender-security-center
			container app-and-browser-protection
				leaf prevent-users-modifying-settings
		container windows-defender-smart-screen
			container explorer
				leaf configure-windows-defender-smart-screen
		container windows-error-reporting
			container advanced-error-reporting-settings {}
			container consent
				leaf configure-default-consent
			leaf automatically-send-memory-dumps-os-generated-error-reports
		container windows-game-recording-and-broadcasting {}
		container windows-hello-for-business {}
		container windows-ink-workspace
			leaf allow-suggested-apps-windows-ink-workspace
			leaf allow-windows-ink-workspace
		container windows-installer
			leaf allow-user-control-over-installs
			leaf always-install-with-elevated-privileges
			leaf prevent-internet-explorer-security-prompt-windows-installer-scripts
		container windows-logon-options
			leaf sign-in-last-interactive-user-automatically-after-system-initiated-restart
		container windows-mail {}
		container windows-media-center {}
		container windows-media-digital-rights-management {}
		container windows-media-player {}
		container windows-meeting-space {}
		container windows-messenger {}
		container windows-mobility-center {}
		container windows-movie-maker {}
		container windows-powershell
			leaf turn-on-powershell-script-block-logging
			leaf turn-on-powershell-transcription
		container windows-reliability-analysis {}
		container windows-remote-management
			container winrm-client
				leaf allow-basic-authentication
				leaf allow-unencrypted-traffic
				leaf disallow-digest-authentication
			container winrm-service
				leaf allow-basic-authentication
				leaf allow-remote-server-management-through-winrm
				leaf allow-unencrypted-traffic
				leaf disallow-winrm-storing-runas-credentials
		container windows-remote-shell
			leaf allow-remote-shell-access
		container windows-side-show {}
		container windows-system-resource-manager {}
		container windows-update
			container windows-update-for-business
				leaf select-when-preview-builds-feature-updates-received
				leaf select-when-quality-updates-received
				leaf manage-preview-builds
			leaf configure-automatic-updates
			leaf configure-automatic-updates-scheduled-install-day
			leaf do-not-adjust-default-install-updates-shutdown-option
			leaf do-not-display-install-updates-shutdown-option
			leaf no-auto-restart-with-logged-on-users-scheduled-automatic-updates-installations
			leaf reschedule-automatic-updates-scheduled-installations
container administrative-templates-user
	container control-panel
		container add-or-remove-programs {}
		container display {}
		container personalization
			leaf enable-screen-saver
			leaf force-specific-screen-saver
			leaf password-protected-screen-saver
			leaf screen-saver-timeout
	container desktop {}
	container network {}
	container shared-folders {}
	container start-menu-and-taskbar
		container notifications
			leaf turn-off-toast-notifications-on-lock-screen
	container system
		container ctrl-alt-del-options {}
		container driver-installation {}
		container folder-redirection {}
		container group-policy {}
		container internet-communication-management
			container internet-communication-settings
				leaf turn-off-help-experience-improvement-program
	container windows-components
		container add-features-to-windows-anytime-upgrade {}
		container app-runtime {}
		container application-compatibility {}
		container attachment-manager
			leaf do-not-preserve-zone-information-in-file-attachments
			leaf notify-antivirus-programs-when-opening-attachments
		container auto-play-policies {}
		container backup {}
		container cloud-content
			leaf configure-windows-spotlight-on-lock-screen
			leaf do-not-suggest-third-party-content-windows-spotlight
			leaf do-not-use-diagnostic-data-for-tailored-experiences
			leaf turn-off-windows-spotlight-features
		container credential-user-interface {}
		container data-collection-and-preview-builds {}
		container desktop-gadgets {}
		container desktop-window-manager {}
		container digital-locker {}
		container edge-ui {}
		container file-explorer-windows-explorer {}
		container file-revocation {}
		container ime {}
		container import-video {}
		container instant-search {}
		container internet-explorer {}
		container location-and-sensors {}
		container microsoft-edge {}
		container microsoft-management-console {}
		container microsoft-user-experience-virtualization {}
		container net-meeting {}
		container network-projector {}
		container network-sharing
			leaf prevent-users-from-sharing-within-their-profile
		container presentation-settings {}
		container remote-desktop-services-terminal-services {}
		container rss-feeds {}
		container search {}
		container sound-recorder {}
		container store {}
		container tablet-pc {}
		container task-scheduler {}
		container windows-calendar {}
		container windows-color-system {}
		container windows-defender-smart-screen {}
		container windows-error-reporting {}
		container windows-hello-for-business {}
		container windows-installer
			leaf always-install-with-elevated-privileges
		container windows-logon-options {}
		container windows-mail {}
		container windows-media-center {}
		container windows-media-player {}
			container networking {}
			container playback
				leaf prevent-codec-download
}
