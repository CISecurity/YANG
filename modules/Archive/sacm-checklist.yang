module sacm-checklist {
	namespace "http://cisecurity.org/yang/sacm-checklist";
	prefix "sacm-checklist";

	//import "ietf-yang-types" {
	//	prefix "yang";
	//}

	organization "Center for Internet Security";
	contact yang@cisecurity.org;
	description "";
	revision 2018-07-14 {
		description 
			"Initial Version; Types, Groupings, and any other constructs common to SACM.";
	}


	// Typedefs
	// Groupings
	// Containers

}


checklist
	checklist-id
	checklist-title
	checklist-description
	...


	checklist-item
		checklits-item-id
		checklist-item-title
		checklist-item-description

		collection
			object (this is something like "file" or "registry" or "user")
			object-keys
				object-key

			// WHAT ABOUT SETs

			behaviors
				// use presence nodes to enable/disable behaviors?
				
			filters
				filter

		evaluation
